# -*- coding: utf-8 -*-
"""
build-cabover.FCMacro — parametric cabover platform + mattress + headboard.

Generates a `cabover` document with simplified solids for:
  - Aluminum ladder + ply deck
  - Olympic queen mattress (66 x 80)
  - Headboard with reading lights placeholder
  - Pass-through door cutout (front bulkhead)
  - Side cubbies

Origin: rear axle / ground. Cabover sits forward of cab back.
Reference: cad/70-interior-cabinetry/cabover/SPECS.md
"""

import FreeCAD as App
import Part
from FreeCAD import Vector

PARAMS = {
    "cabover_x_rear": 3500.0,     # rear edge of cabover (toward main shell)
    "cabover_x_front": 5460.0,    # front edge over cab (= rear + 1960)
    "cab_roof_y": 2180.0,         # F550 cab roof
    "platform_thk": 80.0,         # ladder + ply
    "cabover_width": 2235.0,      # interior shell width
    "mattress_w": 1676.0,         # Olympic queen 66"
    "mattress_l": 2032.0,         # 80"
    "mattress_h": 200.0,          # 8"
    "headboard_thk": 100.0,
    "headboard_h": 760.0,
    "passthru_w": 600.0,
    "passthru_h": 600.0,
}

COLORS = {
    "deck": (0.85, 0.78, 0.55),
    "mattress": (0.95, 0.93, 0.88),
    "headboard": (0.4, 0.45, 0.55),
    "cubby": (0.7, 0.65, 0.5),
    "passthru": (0.8, 0.4, 0.4),
}


def add_box(doc, name, length, width, height, xyz, color=None,
            transparency=0):
    box = Part.makeBox(length, height, width)
    box.translate(Vector(*xyz))
    obj = doc.addObject("Part::Feature", name)
    obj.Shape = box
    if color:
        obj.ViewObject.ShapeColor = color
    if transparency:
        obj.ViewObject.Transparency = transparency
    return obj


def build():
    p = PARAMS
    doc = App.newDocument("cabover")
    rear = p["cabover_x_rear"]
    front = p["cabover_x_front"]
    floor_y = p["cab_roof_y"] + 50.0
    width = p["cabover_width"]

    # Platform deck (ladder + ply combined)
    add_box(doc, "platform_deck",
            front - rear, width, p["platform_thk"],
            (rear, floor_y, -width/2),
            color=COLORS["deck"], transparency=10)

    # Mattress (transverse: width along Z, 80" length along Z, depth along X = 66")
    deck_top = floor_y + p["platform_thk"]
    mattress_x = (front + rear) / 2 - p["mattress_w"] / 2
    mattress_z = -p["mattress_l"] / 2
    add_box(doc, "olympic_queen_mattress",
            p["mattress_w"], p["mattress_l"], p["mattress_h"],
            (mattress_x, deck_top, mattress_z),
            color=COLORS["mattress"])

    # Headboard at front of cabover
    add_box(doc, "headboard",
            p["headboard_thk"], width - 100.0, p["headboard_h"],
            (front - p["headboard_thk"], deck_top,
             -(width - 100.0)/2),
            color=COLORS["headboard"], transparency=15)

    # Side cubbies (port + curb)
    cubby_d = 250.0
    cubby_h = 200.0
    for sign, label in ((+1, "port"), (-1, "curb")):
        z_start = sign * (width/2 - 100.0 - cubby_d)
        add_box(doc, f"cubby_{label}",
                front - rear - 200.0, cubby_d, cubby_h,
                (rear + 100.0, deck_top + p["mattress_h"],
                 z_start),
                color=COLORS["cubby"])

    # Pass-through door (cutout placeholder on front bulkhead)
    add_box(doc, "passthrough_door",
            20.0, p["passthru_w"], p["passthru_h"],
            (rear, floor_y, -p["passthru_w"]/2),
            color=COLORS["passthru"], transparency=20)

    doc.recompute()
    App.Console.PrintMessage(
        "cabover built. Save as cad/70-interior-cabinetry/cabover/"
        "cabover-master.FCStd and export STEP. Verify cab pass-through "
        "alignment against F550 crew cab roof.\n"
    )


if __name__ == "__main__":
    build()
